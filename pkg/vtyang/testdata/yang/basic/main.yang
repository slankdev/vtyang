module main {
  namespace "http://slank.dev/vtyang";
  prefix main;

  typedef month {
    type uint8 {
      range "1..12";
    }
  }
  typedef month-str {
    type enumeration {
      enum January;
      enum February;
      enum March;
      enum April;
      enum May;
      enum June;
      enum July;
      enum August;
      enum September;
      enum October;
      enum November;
      enum December;
    }
  }
  typedef ipv4-address {
    type string {
      pattern
        '(([0-9]|[1-9][0-9]|1[0-9][0-9]|2[0-4][0-9]|25[0-5])\.){3}'
      +  '([0-9]|[1-9][0-9]|1[0-9][0-9]|2[0-4][0-9]|25[0-5])'
      + '(%[\p{N}\p{L}]+)?';
    }
  }
  typedef ipv6-address {
    type string {
      pattern '((:|[0-9a-fA-F]{0,4}):)([0-9a-fA-F]{0,4}:){0,5}'
            + '((([0-9a-fA-F]{0,4}:)?(:|[0-9a-fA-F]{0,4}))|'
            + '(((25[0-5]|2[0-4][0-9]|[01]?[0-9]?[0-9])\.){3}'
            + '(25[0-5]|2[0-4][0-9]|[01]?[0-9]?[0-9])))'
            + '(%[\p{N}\p{L}]+)?';
      pattern '(([^:]+:){6}(([^:]+:[^:]+)|(.*\..*)))|'
            + '((([^:]+:)*[^:]+)?::(([^:]+:)*[^:]+)?)'
            + '(%.+)?';
    }
  }
  typedef ip-address {
    type union {
      type ipv4-address;
      type ipv6-address;
    }
  }
  identity crypto-algo;
  identity aes {
    base crypto-algo;
  }
  identity des3 {
    base crypto-algo;
  }
  identity tcp-app;
  identity http {
    base tcp-app;
  }
  identity ftp {
    base tcp-app;
  }

  container values {
		leaf name { type string;  }
    leaf u08  { type uint8;   }
    leaf u16  { type uint16;  }
    leaf u32  { type uint32;  }
    leaf u64  { type uint64;  }
    leaf i08  { type int8;    }
    leaf i16  { type int16;   }
    leaf i32  { type int32;   }
    leaf i64  { type int64;   }
    leaf bool { type boolean; }
    leaf decimal {
      type decimal64 {
        fraction-digits 2;
      }
    }
    leaf percentage {
      type uint8 {
        range "0..100";
      }
    }
    leaf afi {
      type enumeration {
        enum ipv4;
        enum ipv6;
      }
    }
    leaf month {
      type month;
    }
    leaf month-str {
      type month-str;
    }
    leaf crypto {
      type identityref {
        base crypto-algo;
      }
    }
    container transport-proto {
      choice transport-proto {
        case tcp {
          leaf http-app {
            type string;
          }
        }
        case udp {
          leaf dns-app {
            type string;
          }
        }
      }
    }
    container items {
      list item1 {
        key "name";
        leaf name { type string; }
        leaf description { type string; }
      }
      list item2 {
        key "name type";
        leaf name { type string; }
        leaf type { type string; }
        leaf description { type string; }
      }
      list item3 {
        key "name type vrf";
        leaf name { type string; }
        leaf type { type string; }
        leaf vrf { type string; }
        leaf description { type string; }
      }
      list item4 {
        key "algo";
        leaf algo {
          type identityref {
            base crypto-algo;
          }
        }
        leaf algo2 {
          type identityref {
            base crypto-algo;
          }
        }
        leaf description { type string; }
      }
      list item5 {
        key "algo1 algo2";
        leaf algo1 {
          type identityref {
            base crypto-algo;
          }
        }
        leaf algo2 {
          type identityref {
            base crypto-algo;
          }
        }
        leaf description { type string; }
      }
      list item6 {
        key "algo app";
        leaf algo {
          type identityref {
            base crypto-algo;
          }
        }
        leaf app {
          type identityref {
            base tcp-app;
          }
        }
        leaf description { type string; }
      }
      list item7 {
        key "month";
        leaf month {
          type month-str;
        }
        leaf description { type string; }
      }
      list item8 {
        key "name";
        leaf name {
          type string;
        }
        leaf description { type string; }
      }
      list item9 {
        key "key-string key-uint32 key-uint8";
        leaf key-string {
          type string;
        }
        leaf key-uint32 {
          type uint32;
        }
        leaf key-uint8 {
          type uint8;
        }
        leaf description { type string; }
      }
      list item10 {
        key "address";
        leaf address {
          type ip-address;
        }
        leaf description { type string; }
      }
    }
    leaf ipv4-address { type ipv4-address; }
    leaf ipv6-address { type ipv6-address; }

    // When generating an XML encoding, a value is encoded according
    // to the rules of the member type to which the value belongs.
    // When interpreting an XML encoding, a value is validated
    // consecutively against each member type, in the order they are
    // specified in the "type" statement, until a match is found.
    // The type that matched will be the type of the value for the
    // node that was validated, and the encoding is interpreted
    // according to the rules for that type.
    leaf month-union {
      type union {
        type month-str;
        type month;
      }
    }

    leaf union-multiple {
      type union {
        type union {
          type enumeration {
            enum eva;
          }
          type enumeration {
            enum foo;
            enum bar;
          }
        }
        type enumeration {
          enum hoge;
          enum fuga;
        }
      }
    }

    list union-list {
      key "month";
      leaf month {
        type union {
          type month-str;
          type month;
        }
      }
      leaf description {
        type string;
      }
    }
  }

  // TODO(slankdev): this is in frr modules
  // leafref
  // identityref
  // empty

  // NOTE(slankdev): existance in frr yang modules
  // binary (ietf-routing-types:generalized-label)
  // instance-identifier (vendor/cisco/xr/781/tailf-common-query.yang)
  // bits (vendor/cisco/xr/7822/Cisco-IOS-XR-ipv4-acl-datatypes.yang)
}
