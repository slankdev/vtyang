module main {
  namespace "http://slank.dev/vtyang";
  prefix main;

  container items {
    list items {
      key "name";
      leaf name {
        type string;
      }
      choice ip-version-choice {
        case ipv4-case {
          leaf ipv4-proto {
            type string;
          }
        }
        case ipv6-case {
          leaf ipv6-proto {
            type string;
          }
        }
      }
    }
  }
  container values {
    container transport-proto {
      choice transport-proto-choice {
        case tcp-case {
          leaf tcp-app {
            type string;
          }
        }
        case udp-case {
          leaf udp-app {
            type string;
          }
        }
      }
    }
  }
}
