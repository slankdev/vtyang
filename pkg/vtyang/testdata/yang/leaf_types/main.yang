module main {
  namespace "http://slank.dev/vtyang";
  prefix main;

  typedef route-types-v4 {
    type enumeration {
      enum connected;
      enum static;
      enum bgp;
    }
  }
  typedef route-types-v6 {
    type enumeration {
      enum connected;
      enum static;
      enum bgp;
    }
  }
  typedef month {
    type uint8 {
      range "1..12";
    }
  }
  identity crypto-algo;
  identity aes {
    base crypto-algo;
  }
  identity des3 {
    base crypto-algo;
  }

  container values {
		leaf name { type string;  }
    leaf u08  { type uint8;   }
    leaf u16  { type uint16;  }
    leaf u32  { type uint32;  }
    leaf u64  { type uint64;  }
    leaf i08  { type int8;    }
    leaf i16  { type int16;   }
    leaf i32  { type int32;   }
    leaf i64  { type int64;   }
    leaf bool { type boolean; }
    leaf decimal {
      type decimal64 {
        fraction-digits 2;
      }
    }
    leaf percentage {
      type uint8 {
        range "0..100";
      }
    }
    leaf afi {
      type enumeration {
        enum ipv4;
        enum ipv6;
      }
    }
    leaf union {
      type union {
        type route-types-v4;
        type route-types-v6;
      }
    }
    leaf month {
      type month;
    }
    leaf crypto {
      type identityref {
        base crypto-algo;
      }
    }
    container transport-proto {
      choice transport-proto {
        case tcp {
          leaf http-app {
            type string;
          }
        }
        case udp {
          leaf dns-app {
            type string;
          }
        }
      }
    }
    container items {
      list item1 {
        key "name";
        leaf description { type string; }
      }
      list item2 {
        key "name type";
        leaf name { type string; }
        leaf type { type string; }
        leaf description { type string; }
      }
      list item3 {
        key "name type vrf";
        leaf name { type string; }
        leaf type { type string; }
        leaf vrf { type string; }
        leaf description { type string; }
      }
    }
  }

  // TODO(slankdev): this is in frr modules
  // leafref
  // identityref
  // empty

  // NOTE(slankdev): existance in frr yang modules
  // binary (ietf-routing-types:generalized-label)
  // instance-identifier (vendor/cisco/xr/781/tailf-common-query.yang)
  // bits (vendor/cisco/xr/7822/Cisco-IOS-XR-ipv4-acl-datatypes.yang)
}
