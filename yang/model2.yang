module model2 {
  namespace "http://slank.dev/vtyang";
  prefix model2;

  container users {
    list user  {
      key "name";
      leaf name { type string; }
      leaf mail { type string; }
    }
  }
}
