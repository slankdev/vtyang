module segment-routing {
  namespace "http://frrouting.org/segment-routing";
  prefix segment-routing;

  container segment-routing {
    container srv6 {
      container locators {
        list locator {
          key "name";
          leaf name {
            type string;
          }
          leaf prefix {
            type string;
          }
          leaf prefix-length {
            type uint32;
          }
        }
      }
    }
  }
}
